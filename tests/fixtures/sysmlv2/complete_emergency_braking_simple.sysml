// Generated by ArcLang: SysML v2 in the Arcadia profile (spec/SYSML_PROFILE.md)
package <EmergencyBrakingSystem> 'Automotive Emergency Braking System (AEB)' {
    private import ScalarValues::*;
    private import MeasurementReferences::*;
    private import ISQ::*;
    private import SI::*;
    library package ArcadiaProfile {
        metadata def OA;
        metadata def SA;
        metadata def LA;
        metadata def PA;
        metadata def EPBS;
        metadata def Actor;
        metadata def Entity;
        metadata def Node;
        metadata def Behavior;
        metadata def Hardware;
        metadata def Mission;
        metadata def Capability;
        metadata def Chain;
        metadata def Link;
        metadata def Hazard;
        metadata def Security;
        metadata def PrimaryAsset;
        metadata def Threat;
        metadata def SecurityScales;
        metadata def Configuration;
        metadata def Mode;
        metadata def Class;
        metadata def PhysicalPort;
        metadata def ExchangeItem;
        metadata def Path;
        metadata def Fmea;
        metadata def Interface;
        metadata def Trace {
            attribute rationale : String [0..1];
        }
        metadata def Association;
        metadata def Iterate;
        metadata def Invariant;
        metadata def IoBinding;
        metadata def Twin;
        metadata def Rule;
        metadata def Correspondence;
        metadata def Stakeholder;
        metadata def Region;
        metadata def Beside;
        metadata def Named;
        metadata def Interaction;
    }
    private import ArcadiaProfile::*;
    doc /* Detects an imminent collision, warns the driver and brakes autonomously */
    attribute author : String = "Malek Baroudi";
    attribute safety_standard : String = "ISO 26262 ASIL-D";
    attribute version : String = "2.1.0";
    package Data {
        enum def <'EN-001'> ThreatLevel {
            None;
            Low;
            Critical;
        }
        attribute def <'DT-001'> BrakingForce :> Real {
            attribute base : String = "float";
            attribute unit : String = "N";
        }
        #ExchangeItem item def <'EI-001'> RadarTargets {
            attribute mechanism : String = "FLOW";
            ref item 'element_CL-001' : 'CL-001';
        }
        #ExchangeItem item def <'EI-002'> ThreatAssessed {
            attribute mechanism : String = "EVENT";
            attribute 'element_EN-001' : 'EN-001';
        }
        #ExchangeItem item def <'EI-003'> raw_sensor_data {
            attribute mechanism : String = "FLOW";
            ref item 'element_CL-001' : 'CL-001';
        }
        #ExchangeItem item def <'EI-004'> fused_data {
            attribute mechanism : String = "FLOW";
        }
        #ExchangeItem item def <'EI-005'> tracked_objects {
            attribute mechanism : String = "FLOW";
            ref item 'element_CL-002' : 'CL-002';
        }
        #ExchangeItem item def <'EI-006'> threat_level {
            attribute mechanism : String = "EVENT";
            attribute 'element_EN-001' : 'EN-001';
        }
        #ExchangeItem item def <'EI-007'> vehicle_speed {
            attribute mechanism : String = "FLOW";
        }
        #ExchangeItem item def <'EI-008'> radar_data {
            attribute mechanism : String = "FLOW";
            ref item 'element_CL-001' : 'CL-001';
        }
        #ExchangeItem item def <'EI-009'> camera_data {
            attribute mechanism : String = "FLOW";
        }
        #ExchangeItem item def <'EI-010'> vehicle_state {
            attribute mechanism : String = "FLOW";
        }
        #ExchangeItem item def <'EI-011'> warning_signal {
            attribute mechanism : String = "EVENT";
        }
        #ExchangeItem item def <'EI-012'> brake_command {
            attribute mechanism : String = "FLOW";
            attribute 'element_DT-001' : 'DT-001';
        }
        #Class item def <'CL-001'> RadarFrame {
            attribute range_m : Real;
            attribute azimuth_deg : Real;
            attribute velocity_mps : Real;
        }
        #Class item def <'CL-002'> TrackedObject {
            attribute track_id : Integer;
            attribute time_to_collision_s : Real;
            attribute threat : 'EN-001';
        }
        item def Data;
        item def IBrakeCommand;
        item def ICameraData;
        item def IFusedData;
        item def IRadarData;
        item def IThreatLevel;
        item def ITrackedObjects;
        item def IVehicleSpeed;
        item def IVehicleState;
        item def IWarning;
    }
    #OA package 'Emergency Braking - Operational View' {
        #Entity part <'OE-Vehicle'> Vehicle {
            doc /* The vehicle being controlled */
            perform action <'OA-MonitorEnvironment'> MonitorEnvironment {
                doc /* Continuously observe the surroundings */
            }
            perform action <'OA-DetectThreat'> DetectThreat {
                doc /* Identify a potential collision */
            }
            perform action <'OA-AlertDriver'> AlertDriver {
                doc /* Warn the driver of the imminent danger */
            }
            perform action <'OA-ApplyBrakes'> ApplyBrakes {
                doc /* Brake hard enough to avoid or mitigate the collision */
            }
        }
        #Actor part <'OA-ACT-001'> Driver {
            doc /* Drives the vehicle and keeps the authority over the braking */
            attribute type : String = "human";
        }
        #Actor part <'OA-ACT-002'> Pedestrian {
            doc /* Vulnerable road user the vehicle must not hit */
            attribute type : String = "human";
        }
        #Actor part <'OA-ACT-003'> TrafficEnvironment {
            doc /* Road conditions, weather, other vehicles */
            attribute type : String = "environment";
        }
        #Capability use case <'OC-001'> 'Avoid Collisions' {
            doc /* Avoid collisions with obstacles and vulnerable road users */
        }
        dependency involves from 'OC-001' to 'OA-ACT-001';
        dependency involves from 'OC-001' to 'OA-ACT-002';
        dependency involves from 'OC-001' to 'OA-ACT-003';
        dependency involves from 'OC-001' to 'OE-Vehicle';
        #Interaction connection DriverCommands connect 'OA-ACT-001' to 'OE-Vehicle'.'OA-MonitorEnvironment';
        #Interaction connection EnvironmentData connect 'OA-ACT-003' to 'OE-Vehicle'.'OA-MonitorEnvironment';
        flow ThreatDetection from 'OE-Vehicle'.'OA-MonitorEnvironment' to 'OE-Vehicle'.'OA-DetectThreat';
        #Interaction connection DriverWarning connect 'OE-Vehicle'.'OA-AlertDriver' to 'OA-ACT-001';
        #Interaction connection BrakingAction connect 'OE-Vehicle'.'OA-ApplyBrakes' to 'OE-Vehicle';
        #Interaction connection PedestrianProtection connect 'OE-Vehicle'.'OA-ApplyBrakes' to 'OA-ACT-002';
    }
    #SA package 'AEB System - Functional View' {
        action <'SF-AcquireSensorData'> AcquireSensorData {
            doc /* Collect the radar and camera data */
            attribute latency : DurationValue = 20 [ms];
            attribute safety_level : String = "ASIL-D";
            in item radar_signal : Data::Data;
            in item camera_image : Data::Data;
            out item raw_sensor_data : Data::Data;
            action <'SF-Read_radar'> 'Read radar' {
                doc /* Range, azimuth and relative speed of the echoes */
            }
            action <'SF-Read_camera'> 'Read camera' {
                doc /* Frames of the forward camera */
            }
        }
        action <'SF-FuseData'> FuseData {
            doc /* Combine the radar and camera detections */
            attribute latency : DurationValue = 25 [ms];
            attribute safety_level : String = "ASIL-D";
            in item raw_sensor_data : Data::Data;
            out item fused_data : Data::Data;
        }
        action <'SF-TrackObjects'> TrackObjects {
            doc /* Track the detected objects over time */
            attribute latency : DurationValue = 15 [ms];
            attribute safety_level : String = "ASIL-D";
            in item fused_data : Data::Data;
            out item tracked_objects : Data::Data;
        }
        action <'SF-AssessThreat'> AssessThreat {
            doc /* Compute the time to collision and the threat level */
            attribute latency : DurationValue = 20 [ms];
            attribute safety_level : String = "ASIL-D";
            in item tracked_objects : Data::Data;
            in item vehicle_speed : Data::Data;
            out item threat_level : Data::Data;
        }
        action <'SF-GenerateWarning'> GenerateWarning {
            doc /* Create the driver warning signals */
            attribute safety_level : String = "ASIL-B";
            in item threat_level : Data::Data;
            out item warning_signal : Data::Data;
        }
        action <'SF-ComputeBrakingForce'> ComputeBrakingForce {
            doc /* Calculate the braking force to apply */
            attribute latency : DurationValue = 10 [ms];
            attribute safety_level : String = "ASIL-D";
            in item threat_level : Data::Data;
            in item vehicle_speed : Data::Data;
            out item brake_command : Data::Data;
        }
        action <'SF-MonitorVehicleState'> MonitorVehicleState {
            doc /* Track the vehicle speed, the pedals and the steering */
            attribute safety_level : String = "ASIL-B";
            in item vehicle_can_bus : Data::Data;
            out item vehicle_speed : Data::Data;
        }
        action <'SF-MonitorSystemHealth'> MonitorSystemHealth {
            doc /* Check the sensors and the controller, fall back to a safe state on a fault */
            attribute safety_level : String = "ASIL-D";
        }
        #Actor part <'SA-ACT-Driver'> Driver {
            doc /* Vehicle operator */
        }
        #Actor part <'SA-ACT-Vehicle'> Vehicle {
            doc /* Vehicle platform: brakes, bus, cluster */
        }
        flow SensorToFusion of Data::'EI-003' from 'SF-AcquireSensorData'.raw_sensor_data to 'SF-FuseData'.raw_sensor_data;
        flow FusionToTracking of Data::'EI-004' from 'SF-FuseData'.fused_data to 'SF-TrackObjects'.fused_data;
        flow TrackingToThreat of Data::'EI-005' from 'SF-TrackObjects'.tracked_objects to 'SF-AssessThreat'.tracked_objects;
        flow ThreatToWarning of Data::'EI-006' from 'SF-AssessThreat'.threat_level to 'SF-GenerateWarning'.threat_level;
        flow ThreatToBraking of Data::'EI-006' from 'SF-AssessThreat'.threat_level to 'SF-ComputeBrakingForce'.threat_level;
        flow VehicleToThreat of Data::'EI-007' from 'SF-MonitorVehicleState'.vehicle_speed to 'SF-AssessThreat'.vehicle_speed;
        flow VehicleToBraking of Data::'EI-007' from 'SF-MonitorVehicleState'.vehicle_speed to 'SF-ComputeBrakingForce'.vehicle_speed;
        #Mission use case <'MIS-001'> SafeAutonomousBraking {
            doc /* Prevent collisions through autonomous emergency braking */
        }
        #Capability use case <'CAP-001'> EmergencyBraking {
            doc /* Detect an imminent collision and brake autonomously */
        }
        dependency involves from 'CAP-001' to 'SF-AcquireSensorData';
        dependency involves from 'CAP-001' to 'SF-FuseData';
        dependency involves from 'CAP-001' to 'SF-AssessThreat';
        dependency involves from 'CAP-001' to 'SF-ComputeBrakingForce';
        dependency realizes from 'CAP-001' to 'Emergency Braking - Operational View'::'OC-001';
        dependency mission from 'CAP-001' to 'MIS-001';
        #Chain action <'FC-001'> EmergencyBrakingChain {
            doc /* Sensor acquisition to braking command */
            attribute latency_budget : DurationValue = 100 [ms];
            action step1 :> 'SF-AcquireSensorData';
            then action step2 :> 'SF-FuseData';
            then action step3 :> 'SF-TrackObjects';
            then action step4 :> 'SF-AssessThreat';
            then action step5 :> 'SF-ComputeBrakingForce';
        }
    }
    #SA package 'Safety Requirements' {
        requirement <'REQ-AEB-001'> 'Obstacle detection range' {
            doc /* The system shall detect obstacles at a range of at least 150 m */
            attribute priority : String = "High";
            attribute safety_level : String = "ASIL-D";
        }
        requirement <'REQ-AEB-002'> 'Sensor fusion latency' {
            doc /* Radar and camera data shall be fused within 50 ms */
            attribute priority : String = "High";
            attribute safety_level : String = "ASIL-D";
        }
        requirement <'REQ-AEB-003'> 'Collision risk assessment' {
            doc /* The system shall compute the time to collision of every tracked object */
            attribute priority : String = "High";
            attribute safety_level : String = "ASIL-D";
        }
        requirement <'REQ-AEB-004'> 'Emergency braking activation' {
            doc /* Full braking force shall be commanded within 100 ms of a critical threat detection */
            attribute priority : String = "High";
            attribute safety_level : String = "ASIL-D";
        }
        requirement <'REQ-AEB-005'> 'Driver warning' {
            doc /* The driver shall be warned before autonomous braking is applied */
            attribute priority : String = "Medium";
            attribute safety_level : String = "ASIL-B";
        }
        requirement <'REQ-AEB-006'> 'Driver override' {
            doc /* An accelerator kick-down by the driver shall cancel the autonomous braking */
            attribute priority : String = "High";
            attribute safety_level : String = "ASIL-B";
        }
        requirement <'REQ-AEB-007'> 'Health monitoring' {
            doc /* A sensor or controller fault shall switch the AEB off and request a driver takeover within 200 ms */
            attribute priority : String = "High";
            attribute safety_level : String = "ASIL-D";
        }
    }
    #LA package 'AEB System - Component Structure' {
        port def 'IBrakeCommand port' {
            inout item carried : Data::IBrakeCommand;
        }
        port def 'ICameraData port' {
            inout item carried : Data::ICameraData;
        }
        port def 'IFusedData port' {
            inout item carried : Data::IFusedData;
        }
        port def 'IRadarData port' {
            inout item carried : Data::IRadarData;
        }
        port def 'IThreatLevel port' {
            inout item carried : Data::IThreatLevel;
        }
        port def 'ITrackedObjects port' {
            inout item carried : Data::ITrackedObjects;
        }
        port def 'IVehicleSpeed port' {
            inout item carried : Data::IVehicleSpeed;
        }
        port def 'IVehicleState port' {
            inout item carried : Data::IVehicleState;
        }
        port def 'IWarning port' {
            inout item carried : Data::IWarning;
        }
        part <'LC-RadarSensor'> RadarSensor {
            doc /* Front-facing radar sensor */
            attribute safety_level : String = "ASIL-D";
            attribute type : String = "Sensor";
            out port RadarDataProvider : 'IRadarData port';
            perform action 'Acquire radar frames';
            dependency realizes from 'LC-RadarSensor'::'Acquire radar frames' to 'AEB System - Functional View'::'SF-AcquireSensorData';
        }
        part <'LC-CameraSensor'> CameraSensor {
            doc /* Front-facing camera */
            attribute safety_level : String = "ASIL-D";
            attribute type : String = "Sensor";
            out port CameraDataProvider : 'ICameraData port';
            perform action 'Acquire camera frames';
            dependency realizes from 'LC-CameraSensor'::'Acquire camera frames' to 'AEB System - Functional View'::'SF-AcquireSensorData';
        }
        part <'LC-SensorFusion'> SensorFusion {
            doc /* Multi-sensor data fusion */
            attribute safety_level : String = "ASIL-D";
            attribute type : String = "Processing";
            in port RadarDataConsumer : 'IRadarData port';
            in port CameraDataConsumer : 'ICameraData port';
            out port FusedDataProvider : 'IFusedData port';
            perform action 'Fuse sensor data';
            dependency realizes from 'LC-SensorFusion'::'Fuse sensor data' to 'AEB System - Functional View'::'SF-FuseData';
        }
        part <'LC-ObjectTracker'> ObjectTracker {
            doc /* Object tracking and motion prediction */
            attribute safety_level : String = "ASIL-D";
            attribute type : String = "Processing";
            in port FusedDataConsumer : 'IFusedData port';
            out port TrackedObjectsProvider : 'ITrackedObjects port';
            perform action 'Track objects';
            dependency realizes from 'LC-ObjectTracker'::'Track objects' to 'AEB System - Functional View'::'SF-TrackObjects';
        }
        part <'LC-ThreatAssessment'> ThreatAssessment {
            doc /* Collision risk assessment */
            attribute safety_level : String = "ASIL-D";
            attribute type : String = "Decision";
            in port TrackedObjectsConsumer : 'ITrackedObjects port';
            in port VehicleStateConsumer : 'IVehicleState port';
            out port ThreatLevelProvider : 'IThreatLevel port';
            out port WarningProvider : 'IWarning port';
            perform action 'Assess collision threat';
            dependency realizes from 'LC-ThreatAssessment'::'Assess collision threat' to 'AEB System - Functional View'::'SF-AssessThreat';
            perform action 'Request the warning';
            dependency realizes from 'LC-ThreatAssessment'::'Request the warning' to 'AEB System - Functional View'::'SF-GenerateWarning';
        }
        part <'LC-BrakeController'> BrakeController {
            doc /* Emergency brake control */
            attribute safety_level : String = "ASIL-D";
            attribute type : String = "Controller";
            in port ThreatLevelConsumer : 'IThreatLevel port';
            in port VehicleSpeedConsumer : 'IVehicleSpeed port';
            out port BrakeCommandProvider : 'IBrakeCommand port';
            perform action 'Compute braking command';
            dependency realizes from 'LC-BrakeController'::'Compute braking command' to 'AEB System - Functional View'::'SF-ComputeBrakingForce';
            perform action 'Release on driver override' {
                doc /* Accelerator kick-down cancels the autonomous braking */
            }
        }
        part <'LC-DriverInterface'> DriverInterface {
            doc /* HMI for the warnings */
            attribute safety_level : String = "QM";
            attribute type : String = "Interface";
            in port WarningConsumer : 'IWarning port';
            perform action 'Warn driver';
            dependency realizes from 'LC-DriverInterface'::'Warn driver' to 'AEB System - Functional View'::'SF-GenerateWarning';
        }
        part <'LC-VehicleCANGateway'> VehicleCANGateway {
            doc /* Interface to the vehicle CAN bus: speed, pedals, steering */
            attribute safety_level : String = "ASIL-B";
            attribute type : String = "Gateway";
            out port VehicleStateProvider : 'IVehicleState port';
            out port VehicleSpeedProvider : 'IVehicleSpeed port';
            perform action 'Relay vehicle state';
            dependency realizes from 'LC-VehicleCANGateway'::'Relay vehicle state' to 'AEB System - Functional View'::'SF-MonitorVehicleState';
        }
        part <'LC-BrakeActuator'> BrakeActuator {
            doc /* Brake actuation on the hydraulic unit */
            attribute safety_level : String = "ASIL-D";
            attribute type : String = "Actuator";
            in port BrakeCommandConsumer : 'IBrakeCommand port';
            perform action 'Apply braking force';
            dependency realizes from 'LC-BrakeActuator'::'Apply braking force' to 'AEB System - Functional View'::'SF-ComputeBrakingForce';
        }
        part <'LC-SystemSupervisor'> SystemSupervisor {
            doc /* Health monitoring of the sensors and the controller */
            attribute safety_level : String = "ASIL-D";
            attribute type : String = "Supervisor";
            in port FusedDataConsumer : 'IFusedData port';
            perform action 'Monitor system health';
            dependency realizes from 'LC-SystemSupervisor'::'Monitor system health' to 'AEB System - Functional View'::'SF-MonitorSystemHealth';
            perform action 'Handle faults' {
                doc /* Switch the AEB off and request a takeover */
            }
        }
        connection 'Radar Data' connect 'LC-RadarSensor'.RadarDataProvider to 'LC-SensorFusion'.RadarDataConsumer {
            attribute label : String = "Radar Data";
        }
        connection 'Camera Data' connect 'LC-CameraSensor'.CameraDataProvider to 'LC-SensorFusion'.CameraDataConsumer {
            attribute label : String = "Camera Data";
        }
        connection 'Fused Data' connect 'LC-SensorFusion'.FusedDataProvider to 'LC-ObjectTracker'.FusedDataConsumer {
            attribute label : String = "Fused Data";
        }
        connection 'Fused Data (monitoring)' connect 'LC-SensorFusion'.FusedDataProvider to 'LC-SystemSupervisor'.FusedDataConsumer {
            attribute label : String = "Fused Data (monitoring)";
        }
        connection 'Tracked Objects' connect 'LC-ObjectTracker'.TrackedObjectsProvider to 'LC-ThreatAssessment'.TrackedObjectsConsumer {
            attribute label : String = "Tracked Objects";
        }
        connection 'Vehicle State' connect 'LC-VehicleCANGateway'.VehicleStateProvider to 'LC-ThreatAssessment'.VehicleStateConsumer {
            attribute label : String = "Vehicle State";
        }
        connection 'Threat Level' connect 'LC-ThreatAssessment'.ThreatLevelProvider to 'LC-BrakeController'.ThreatLevelConsumer {
            attribute label : String = "Threat Level";
        }
        connection Warning connect 'LC-ThreatAssessment'.WarningProvider to 'LC-DriverInterface'.WarningConsumer {
            attribute label : String = "Warning";
        }
        connection 'Vehicle Speed' connect 'LC-VehicleCANGateway'.VehicleSpeedProvider to 'LC-BrakeController'.VehicleSpeedConsumer {
            attribute label : String = "Vehicle Speed";
        }
        connection 'Brake Command' connect 'LC-BrakeController'.BrakeCommandProvider to 'LC-BrakeActuator'.BrakeCommandConsumer {
            attribute label : String = "Brake Command";
        }
    }
    #PA package 'AEB System - Hardware Deployment' {
        #Node part <'PN-FrontRadarECU'> FrontRadarECU {
            doc /* Radar sensor ECU */
            attribute memory : String = "512 KB Flash, 128 KB RAM";
            attribute node_type : String = "ECU";
            attribute processor : String = "ARM Cortex-M4";
            attribute safety_level : String = "ASIL-D";
            #Behavior part <'BC-RadarProcessing'> RadarProcessing {
                doc /* Radar data acquisition and preprocessing */
                attribute safety_level : String = "ASIL-D";
            }
        }
        #Node part <'PN-FrontCameraECU'> FrontCameraECU {
            doc /* Camera sensor ECU */
            attribute node_type : String = "ECU";
            attribute processor : String = "ARM Cortex-A53";
            attribute ram : StorageCapacityValue = 2 [GB];
            attribute safety_level : String = "ASIL-D";
            #Behavior part <'BC-CameraProcessing'> CameraProcessing {
                doc /* Camera image processing and object detection */
                attribute safety_level : String = "ASIL-D";
            }
        }
        #Node part <'PN-CentralADASECU'> CentralADASECU {
            doc /* Central ADAS processing unit */
            attribute node_type : String = "ECU";
            attribute processor : String = "Intel Atom x5-E3940";
            attribute ram : StorageCapacityValue = 8 [GB];
            attribute safety_level : String = "ASIL-D";
            attribute storage : StorageCapacityValue = 64 [GB];
            #Behavior part <'BC-FusionModule'> FusionModule {
                attribute safety_level : String = "ASIL-D";
            }
            #Behavior part <'BC-TrackingModule'> TrackingModule {
                attribute safety_level : String = "ASIL-D";
            }
            #Behavior part <'BC-ThreatModule'> ThreatModule {
                attribute safety_level : String = "ASIL-D";
            }
            #Behavior part <'BC-BrakingModule'> BrakingModule {
                attribute safety_level : String = "ASIL-D";
            }
            #Behavior part <'BC-SupervisorModule'> SupervisorModule {
                attribute safety_level : String = "ASIL-D";
            }
        }
        #Node part <'PN-BrakeECU'> BrakeECU {
            doc /* Electronic brake control unit */
            attribute memory : String = "8 MB Flash, 3 MB RAM";
            attribute node_type : String = "ECU";
            attribute processor : String = "Infineon AURIX TC397";
            attribute safety_level : String = "ASIL-D";
            #Behavior part <'BC-BrakeActuation'> BrakeActuation {
                attribute safety_level : String = "ASIL-D";
            }
        }
        #Node part <'PN-InstrumentCluster'> InstrumentCluster {
            doc /* Driver display and HMI */
            attribute node_type : String = "ECU";
            attribute processor : String = "NXP i.MX 8M";
            attribute ram : StorageCapacityValue = 4 [GB];
            attribute safety_level : String = "QM";
            #Behavior part <'BC-HMI'> HMI {
                attribute safety_level : String = "QM";
            }
        }
        #Node part <'PN-CANGatewayECU'> CANGatewayECU {
            doc /* Vehicle CAN gateway */
            attribute flash : StorageCapacityValue = 2 [MB];
            attribute node_type : String = "Gateway";
            attribute processor : String = "Renesas RH850";
            attribute safety_level : String = "ASIL-B";
            #Behavior part <'BC-CANInterface'> CANInterface {
                attribute safety_level : String = "ASIL-B";
            }
        }
        allocate 'AEB System - Component Structure'::'LC-RadarSensor' to 'PN-FrontRadarECU';
        dependency allocated_component from 'PN-FrontRadarECU'::'BC-RadarProcessing' to 'AEB System - Component Structure'::'LC-RadarSensor';
        allocate 'AEB System - Component Structure'::'LC-CameraSensor' to 'PN-FrontCameraECU';
        dependency allocated_component from 'PN-FrontCameraECU'::'BC-CameraProcessing' to 'AEB System - Component Structure'::'LC-CameraSensor';
        allocate 'AEB System - Component Structure'::'LC-SensorFusion' to 'PN-CentralADASECU';
        allocate 'AEB System - Component Structure'::'LC-ObjectTracker' to 'PN-CentralADASECU';
        allocate 'AEB System - Component Structure'::'LC-ThreatAssessment' to 'PN-CentralADASECU';
        allocate 'AEB System - Component Structure'::'LC-BrakeController' to 'PN-CentralADASECU';
        allocate 'AEB System - Component Structure'::'LC-SystemSupervisor' to 'PN-CentralADASECU';
        dependency allocated_component from 'PN-CentralADASECU'::'BC-FusionModule' to 'AEB System - Component Structure'::'LC-SensorFusion';
        dependency allocated_component from 'PN-CentralADASECU'::'BC-TrackingModule' to 'AEB System - Component Structure'::'LC-ObjectTracker';
        dependency allocated_component from 'PN-CentralADASECU'::'BC-ThreatModule' to 'AEB System - Component Structure'::'LC-ThreatAssessment';
        dependency allocated_component from 'PN-CentralADASECU'::'BC-BrakingModule' to 'AEB System - Component Structure'::'LC-BrakeController';
        dependency allocated_component from 'PN-CentralADASECU'::'BC-SupervisorModule' to 'AEB System - Component Structure'::'LC-SystemSupervisor';
        allocate 'AEB System - Component Structure'::'LC-BrakeActuator' to 'PN-BrakeECU';
        dependency allocated_component from 'PN-BrakeECU'::'BC-BrakeActuation' to 'AEB System - Component Structure'::'LC-BrakeActuator';
        allocate 'AEB System - Component Structure'::'LC-DriverInterface' to 'PN-InstrumentCluster';
        dependency allocated_component from 'PN-InstrumentCluster'::'BC-HMI' to 'AEB System - Component Structure'::'LC-DriverInterface';
        allocate 'AEB System - Component Structure'::'LC-VehicleCANGateway' to 'PN-CANGatewayECU';
        dependency allocated_component from 'PN-CANGatewayECU'::'BC-CANInterface' to 'AEB System - Component Structure'::'LC-VehicleCANGateway';
        #Link connection CANBus connect 'PN-FrontRadarECU' to 'PN-CentralADASECU' {
            attribute bandwidth : BinaryDigitRateValue = 5 ['Mbit/s'];
            attribute protocol : String = "CAN FD";
        }
        #Link connection EthernetLink connect 'PN-FrontCameraECU' to 'PN-CentralADASECU' {
            attribute bandwidth : BinaryDigitRateValue = 1 ['Gbit/s'];
            attribute protocol : String = "Automotive Ethernet";
        }
        #Link connection BrakeCAN connect 'PN-CentralADASECU' to 'PN-BrakeECU' {
            attribute bandwidth : BinaryDigitRateValue = 5 ['Mbit/s'];
            attribute protocol : String = "CAN FD";
        }
        #Link connection VehicleCAN connect 'PN-CANGatewayECU' to 'PN-CentralADASECU' {
            attribute bandwidth : BinaryDigitRateValue = 500 ['kbit/s'];
            attribute protocol : String = "CAN";
        }
        #Link connection DisplayLink connect 'PN-CentralADASECU' to 'PN-InstrumentCluster' {
            attribute bandwidth : BinaryDigitRateValue = 3.2 ['Gbit/s'];
            attribute protocol : String = "LVDS";
        }
        connection RadarMessages connect 'PN-FrontRadarECU' to 'PN-CentralADASECU' {
            attribute frequency : FrequencyValue = 50 [Hz];
            attribute message_type : String = "RadarTargets";
        }
        dependency 'via' from RadarMessages to CANBus;
        connection CameraMessages connect 'PN-FrontCameraECU' to 'PN-CentralADASECU' {
            attribute frequency : FrequencyValue = 30 [Hz];
            attribute message_type : String = "CameraFrame";
        }
        dependency 'via' from CameraMessages to EthernetLink;
        connection BrakeCommands connect 'PN-CentralADASECU' to 'PN-BrakeECU' {
            attribute frequency : FrequencyValue = 100 [Hz];
            attribute message_type : String = "BrakeRequest";
        }
        dependency 'via' from BrakeCommands to BrakeCAN;
        connection VehicleStatus connect 'PN-CANGatewayECU' to 'PN-CentralADASECU' {
            attribute frequency : FrequencyValue = 100 [Hz];
            attribute message_type : String = "VehicleSpeed";
        }
        dependency 'via' from VehicleStatus to VehicleCAN;
    }
    package Behaviors {
        state AEBOperatingModes {
            entry; then Standby;
            #Mode state Standby {
                doc /* System armed, monitoring */
            }
            #Mode state Warning {
                doc /* Threat detected, driver warned */
            }
            #Mode state EmergencyBraking {
                doc /* Autonomous braking active */
            }
            state Failed {
                doc /* Undergone: sensor or actuator failure, driver takeover requested */
            }
            transition t1 first Standby then Warning {
                attribute trigger : String = "AssessThreat";
            }
            transition t2 first Warning then EmergencyBraking {
                attribute trigger : String = "ComputeBrakingForce";
            }
            transition t3 first EmergencyBraking then Standby {
                attribute guard : String = "vehicle stopped or threat gone";
                attribute trigger : String = "MonitorVehicleState";
            }
            transition t4 first EmergencyBraking then Standby {
                attribute guard : String = "accelerator kick-down";
                attribute trigger : String = "Release on driver override";
            }
            transition t5 first Standby then Failed {
                attribute guard : String = "sensor fault";
                attribute trigger : String = "Handle faults";
            }
        }
        occurrence EmergencyStop {
            ref part l_RadarSensor :> 'AEB System - Component Structure'::'LC-RadarSensor' {
                event occurrence m1_sent;
            }
            ref part l_SensorFusion :> 'AEB System - Component Structure'::'LC-SensorFusion' {
                event occurrence m1_received;
                then event occurrence m2_sent;
            }
            ref part l_ThreatAssessment :> 'AEB System - Component Structure'::'LC-ThreatAssessment' {
                event occurrence m2_received;
                then event occurrence m3_sent;
                then event occurrence m4_sent;
            }
            ref part l_DriverInterface :> 'AEB System - Component Structure'::'LC-DriverInterface' {
                event occurrence m3_received;
            }
            ref part l_BrakeController :> 'AEB System - Component Structure'::'LC-BrakeController' {
                event occurrence m4_received;
                then event occurrence m5_sent;
            }
            ref part l_BrakeActuator :> 'AEB System - Component Structure'::'LC-BrakeActuator' {
                event occurrence m5_received;
            }
            message <m1> 'raw radar targets' from l_RadarSensor.m1_sent to l_SensorFusion.m1_received;
            message <m2> 'fused object list' from l_SensorFusion.m2_sent to l_ThreatAssessment.m2_received;
            message <m3> 'collision warning' from l_ThreatAssessment.m3_sent to l_DriverInterface.m3_received;
            message <m4> 'critical threat' from l_ThreatAssessment.m4_sent to l_BrakeController.m4_received;
            message <m5> 'full braking force' from l_BrakeController.m5_sent to l_BrakeActuator.m5_received;
        }
    }
    package Safety {
        #Hazard requirement <'HAZ-001'> 'Unintended full braking on highway' {
            attribute asil : String = "ASIL-D";
            attribute controllability : String = "C3";
            attribute exposure : String = "E4";
            attribute severity : String = "S3";
        }
        dependency mitigated_by from 'HAZ-001' to 'Safety Requirements'::'REQ-AEB-003';
        dependency mitigated_by from 'HAZ-001' to 'Safety Requirements'::'REQ-AEB-004';
        dependency mitigated_by from 'HAZ-001' to 'Safety Requirements'::'REQ-AEB-006';
        #Hazard requirement <'HAZ-002'> 'No braking on imminent collision' {
            attribute asil : String = "ASIL-C";
            attribute controllability : String = "C3";
            attribute exposure : String = "E3";
            attribute severity : String = "S3";
        }
        dependency mitigated_by from 'HAZ-002' to 'Safety Requirements'::'REQ-AEB-001';
        dependency mitigated_by from 'HAZ-002' to 'Safety Requirements'::'REQ-AEB-002';
        dependency mitigated_by from 'HAZ-002' to 'Safety Requirements'::'REQ-AEB-007';
        #Hazard requirement <'HAZ-003'> 'Late driver warning' {
            attribute asil : String = "ASIL-B";
            attribute controllability : String = "C2";
            attribute exposure : String = "E4";
            attribute severity : String = "S2";
        }
        dependency mitigated_by from 'HAZ-003' to 'Safety Requirements'::'REQ-AEB-005';
    }
    verification <'TC-001'> 'Radar range verification' {
        doc /* Verify 150 m obstacle detection on the proving ground */
        attribute verdict : String = "pass";
        attribute method : String = "test";
        objective {
            verify 'Safety Requirements'::'REQ-AEB-001';
        }
    }
    verification <'TC-002'> 'Fusion latency measurement' {
        doc /* Measure the radar and camera fusion latency under full bus load */
        attribute verdict : String = "pass";
        attribute method : String = "test";
        objective {
            verify 'Safety Requirements'::'REQ-AEB-002';
        }
    }
    verification <'TC-003'> 'TTC computation analysis' {
        doc /* Worst-case execution time analysis of the TTC algorithm */
        attribute verdict : String = "pass";
        attribute method : String = "analysis";
        objective {
            verify 'Safety Requirements'::'REQ-AEB-003';
        }
    }
    verification <'TC-004'> 'Emergency braking activation test' {
        doc /* Full braking force commanded within 100 ms on the target dummy */
        attribute verdict : String = "pass";
        attribute method : String = "test";
        objective {
            verify 'Safety Requirements'::'REQ-AEB-004';
        }
    }
    verification <'TC-005'> 'Driver warning demonstration' {
        doc /* Visual and audio warning precedes the autonomous braking */
        attribute verdict : String = "pass";
        attribute method : String = "demonstration";
        objective {
            verify 'Safety Requirements'::'REQ-AEB-005';
        }
    }
    verification <'TC-006'> 'Driver override demonstration' {
        doc /* Kick-down during autonomous braking releases the brakes */
        attribute verdict : String = "pass";
        attribute method : String = "demonstration";
        objective {
            verify 'Safety Requirements'::'REQ-AEB-006';
        }
    }
    verification <'TC-007'> 'Fault injection campaign' {
        doc /* Radar and controller faults injected on the HIL bench, takeover requested within 200 ms */
        attribute verdict : String = "pass";
        attribute method : String = "test";
        objective {
            verify 'Safety Requirements'::'REQ-AEB-007';
        }
    }
    assert constraint <'CST-001'> 'Braking chain within budget' {
        NumericalFunctions::sum(('AEB System - Functional View'::'SF-AcquireSensorData'.latency, 'AEB System - Functional View'::'SF-FuseData'.latency, 'AEB System - Functional View'::'SF-TrackObjects'.latency, 'AEB System - Functional View'::'SF-AssessThreat'.latency, 'AEB System - Functional View'::'SF-ComputeBrakingForce'.latency)) <= 'AEB System - Functional View'::'FC-001'.latency_budget
    }
    satisfy 'Safety Requirements'::'REQ-AEB-001' by 'AEB System - Component Structure'::'LC-RadarSensor' { @Trace { rationale = "150 m long-range radar detection"; } }
    satisfy 'Safety Requirements'::'REQ-AEB-001' by 'AEB System - Component Structure'::'LC-CameraSensor' { @Trace { rationale = "Visual obstacle confirmation"; } }
    satisfy 'Safety Requirements'::'REQ-AEB-002' by 'AEB System - Component Structure'::'LC-SensorFusion' { @Trace { rationale = "Fuses radar and camera within the latency budget"; } }
    satisfy 'Safety Requirements'::'REQ-AEB-003' by 'AEB System - Component Structure'::'LC-ObjectTracker' { @Trace { rationale = "Consistent tracks are the input of the time to collision"; } }
    satisfy 'Safety Requirements'::'REQ-AEB-003' by 'AEB System - Component Structure'::'LC-ThreatAssessment' { @Trace { rationale = "Computes the time to collision of every tracked object"; } }
    satisfy 'Safety Requirements'::'REQ-AEB-004' by 'AEB System - Component Structure'::'LC-BrakeController' { @Trace { rationale = "Commands full braking force on a critical threat"; } }
    satisfy 'Safety Requirements'::'REQ-AEB-004' by 'AEB System - Component Structure'::'LC-BrakeActuator' { @Trace { rationale = "Builds up the full brake pressure within the budget"; } }
    satisfy 'Safety Requirements'::'REQ-AEB-005' by 'AEB System - Component Structure'::'LC-DriverInterface' { @Trace { rationale = "Issues the visual and audio warnings"; } }
    satisfy 'Safety Requirements'::'REQ-AEB-006' by 'AEB System - Component Structure'::'LC-VehicleCANGateway' { @Trace { rationale = "Relays the accelerator pedal state to the brake controller"; } }
    satisfy 'Safety Requirements'::'REQ-AEB-006' by 'AEB System - Component Structure'::'LC-BrakeController' { @Trace { rationale = "Releases the braking on the kick-down"; } }
    satisfy 'Safety Requirements'::'REQ-AEB-007' by 'AEB System - Component Structure'::'LC-SystemSupervisor' { @Trace { rationale = "Monitors the sensors and the controller, requests the takeover"; } }
    dependency realizes from 'AEB System - Functional View'::'SF-AcquireSensorData' to 'Emergency Braking - Operational View'::'OE-Vehicle'::'OA-MonitorEnvironment' { @Trace { rationale = "Sensor acquisition realizes environment monitoring"; } }
    dependency realizes from 'AEB System - Functional View'::'SF-AssessThreat' to 'Emergency Braking - Operational View'::'OE-Vehicle'::'OA-DetectThreat' { @Trace { rationale = "Threat assessment realizes threat detection"; } }
    dependency realizes from 'AEB System - Functional View'::'SF-GenerateWarning' to 'Emergency Braking - Operational View'::'OE-Vehicle'::'OA-AlertDriver' { @Trace { rationale = "The warning realizes the driver alert"; } }
    dependency realizes from 'AEB System - Functional View'::'SF-ComputeBrakingForce' to 'Emergency Braking - Operational View'::'OE-Vehicle'::'OA-ApplyBrakes' { @Trace { rationale = "Braking computation realizes brake application"; } }
    view 'Braking chain' {
        attribute 'view' : String = "lab";
        expose 'AEB System - Component Structure'::'LC-SensorFusion';
        expose 'AEB System - Component Structure'::'LC-ThreatAssessment';
        expose 'AEB System - Component Structure'::'LC-BrakeController';
        expose 'AEB System - Component Structure'::'LC-BrakeActuator';
    }
    view 'Around the brake ECU' {
        attribute 'view' : String = "pab";
        attribute context : Boolean = true;
        expose 'AEB System - Hardware Deployment'::'PN-BrakeECU';
    }
    package ArcLangUnits {
        private import MeasurementReferences::*;
        private import ISQ::*;
        private import SI::*;
        attribute <'Gbit/s'> 'gigabit per second' : BinaryDigitRateUnit { :>> unitConversion: ConversionByPrefix { :>> prefix = giga; :>> referenceUnit = 'bit/s'; } }
        attribute <'Mbit/s'> 'megabit per second' : BinaryDigitRateUnit { :>> unitConversion: ConversionByPrefix { :>> prefix = mega; :>> referenceUnit = 'bit/s'; } }
        attribute <'kbit/s'> 'kilobit per second' : BinaryDigitRateUnit { :>> unitConversion: ConversionByPrefix { :>> prefix = kilo; :>> referenceUnit = 'bit/s'; } }
        attribute <GB> gigabyte : StorageCapacityUnit { :>> unitConversion: ConversionByPrefix { :>> prefix = giga; :>> referenceUnit = B; } }
        attribute <MB> megabyte : StorageCapacityUnit { :>> unitConversion: ConversionByPrefix { :>> prefix = mega; :>> referenceUnit = B; } }
        attribute <ms> millisecond : DurationUnit { :>> unitConversion: ConversionByPrefix { :>> prefix = milli; :>> referenceUnit = s; } }
    }
    private import ArcLangUnits::*;
}
