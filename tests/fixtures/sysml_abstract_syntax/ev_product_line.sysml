// Generated by ArcLang: SysML v2 in the Arcadia profile (spec/SYSML_PROFILE.md)
package 'EV product line' {
    private import ScalarValues::*;
    private import MeasurementReferences::*;
    private import ISQ::*;
    private import SI::*;
    library package ArcadiaProfile {
        metadata def OA;
        metadata def SA;
        metadata def LA;
        metadata def PA;
        metadata def EPBS;
        metadata def Actor;
        metadata def Entity;
        metadata def Node;
        metadata def Behavior;
        metadata def Hardware;
        metadata def Mission;
        metadata def Capability;
        metadata def Chain;
        metadata def Link;
        metadata def Hazard;
        metadata def Security;
        metadata def PrimaryAsset;
        metadata def Threat;
        metadata def SecurityScales;
        metadata def Configuration;
        metadata def Mode;
        metadata def Class;
        metadata def PhysicalPort;
        metadata def ExchangeItem;
        metadata def Path;
        metadata def Fmea;
        metadata def Interface;
        metadata def Trace;
        metadata def Association;
        metadata def Iterate;
        metadata def Invariant;
    }
    private import ArcadiaProfile::*;
    package Tags {
        metadata def Safety;
    }
    private import Tags::*;
    doc /* Two batteries, two chargers, one architecture */
    package Data {
        item def Data;
        item def 'HVIL 800 V';
    }
    #SA package 'Vehicle needs' {
        requirement 'REQ-RANGE' {
            doc /* Enough energy on board for the range of the line */
        }
        requirement 'REQ-ISO' {
            doc /* High voltage is monitored for isolation faults */
        }
    }
    #LA package EV {
        port def 'HVIL 800 V port' {
            inout item carried : Data::'HVIL 800 V';
        }
        part <'LC-EV'> Vehicle {
            attribute energy : EnergyValue = 60 ['kW*h'];
            part def 'Battery variation' {
                @Safety;
                inout port hv : Types::'HV connector';
            }
            variation part <'LC-BATT'> Battery : 'Battery variation' {
                variant part <'LC-PACK-STD'> 'Standard pack' {
                    attribute energy : EnergyValue = 64 ['kW*h'];
                }
                variant part <'LC-PACK-LR'> 'Long range pack' {
                    attribute energy : EnergyValue = 82 ['kW*h'];
                }
            }
            part def 'Charger variation' {
                inout port hv : Types::'HV connector';
            }
            variation part <'LC-CHG'> Charger : 'Charger variation' {
                variant part <'LC-OBC-11'> '11 kW onboard charger';
                variant part <'LC-OBC-22'> '22 kW onboard charger';
            }
            part <'LC-BMS'> 'Battery management' {
                @Safety;
            }
            part <'LC-INFO'> Infotainment;
        }
        connection 'Charging power' : Types::'HV power' connect 'LC-EV'.'LC-CHG'.hv.pole to 'LC-EV'.'LC-BATT'.hv.pole;
    }
    #PA package 'EV hardware' {
        #Node part <'PN-BECU'> 'Battery ECU';
    }
    package Types {
        port def 'Data port' {
            inout item carried : Data::Data;
        }
        abstract port def 'HV connector' {
            attribute 'interface' : String default = "HVIL 800 V";
            inout port pole : 'Data port' [2];
        }
        abstract connection def 'HV power' {
            end source;
            end target;
            attribute protocol : String default = "DC 800 V";
        }
        abstract allocation def 'Software deployment' {
            end source;
            end target;
            attribute from_kind : String default = "PhysicalNode";
            attribute partition : String default = "ASIL-C partition";
            attribute to_kind : String default = "LogicalComponent";
        }
    }
    #Configuration part <'CFG-CITY'> City;
    dependency selects from 'CFG-CITY' to EV::'LC-EV'::'LC-BATT'::'LC-PACK-STD';
    dependency selects from 'CFG-CITY' to EV::'LC-EV'::'LC-CHG'::'LC-OBC-11';
    #Configuration part <'CFG-TOURING'> Touring;
    dependency selects from 'CFG-TOURING' to EV::'LC-EV'::'LC-BATT'::'LC-PACK-LR';
    dependency selects from 'CFG-TOURING' to EV::'LC-EV'::'LC-CHG'::'LC-OBC-22';
    verification <'TC-RANGE'> 'Range analysis' {
        attribute method : String = "analysis";
        objective {
            verify 'Vehicle needs'::'REQ-RANGE';
        }
        assert 'CST-RANGE';
    }
    verification <'TC-ISO'> 'Isolation fault injection' {
        attribute verdict : String = "pass";
        attribute method : String = "test";
        objective {
            verify 'Vehicle needs'::'REQ-ISO';
        }
    }
    constraint <'CST-RANGE'> 'Smallest pack covers the range' {
        attribute expression : String = "\"LC-PACK-STD\".energy >= \"LC-EV\".energy";
        // not an expression of the export: 'LC-PACK-STD' is a variant or in one, which SysML v2 reaches only inside its variation
    }
    allocation : Types::'Software deployment' allocate 'EV hardware'::'PN-BECU' to EV::'LC-EV'.'LC-BMS';
    satisfy 'Vehicle needs'::'REQ-RANGE' by EV::'LC-EV'.'LC-BATT';
    satisfy 'Vehicle needs'::'REQ-ISO' by EV::'LC-EV'.'LC-BMS';
    view 'Touring car' {
        attribute 'view' : String = "lab";
        attribute configuration : String = "CFG-TOURING";
        expose EV::'LC-EV';
    }
    view 'Safety relevant' {
        attribute 'view' : String = "lab";
        expose EV::'LC-EV'::**;
        filter @Safety;
    }
    package ArcLangUnits {
        private import MeasurementReferences::*;
        private import ISQ::*;
        private import SI::*;
        attribute <'kW*h'> 'kilowatt hour' : EnergyUnit { :>> unitConversion: ConversionByConvention { :>> referenceUnit = J; :>> conversionFactor = 3600000; } }
    }
    private import ArcLangUnits::*;
}
