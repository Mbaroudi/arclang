// Generated by ArcLang: SysML v2 in the Arcadia profile (spec/SYSML_PROFILE.md)
package LaneKeepingTiming {
    private import ScalarValues::*;
    private import MeasurementReferences::*;
    private import ISQ::*;
    private import SI::*;
    library package ArcadiaProfile {
        metadata def OA;
        metadata def SA;
        metadata def LA;
        metadata def PA;
        metadata def EPBS;
        metadata def Actor;
        metadata def Entity;
        metadata def Node;
        metadata def Behavior;
        metadata def Hardware;
        metadata def Mission;
        metadata def Capability;
        metadata def Chain;
        metadata def Link;
        metadata def Hazard;
        metadata def Mode;
        metadata def Class;
        metadata def PhysicalPort;
        metadata def ExchangeItem;
        metadata def Path;
        metadata def Fmea;
        metadata def Interface;
        metadata def Trace;
        metadata def Association;
        metadata def Iterate;
        metadata def Invariant;
    }
    private import ArcadiaProfile::*;
    doc /* Lane keeping assist: end-to-end timing and bus load constraints */
    attribute version : String = "1.0";
    package Data {
        item def Data;
        item def DepartureEstimate;
        item def LaneModel;
    }
    #OA package Driving {
        #Actor part <'ACT-DRV'> Driver;
    }
    #SA package 'Lane Keeping Assist' {
        action <'SF-DET'> 'Detect lane markings' : Types::'Periodic task' {
            attribute latency : DurationValue = 30 [ms];
            attribute :>> period = 33 [ms];
            attribute wcet : DurationValue = 0.035 [s];
            out item lane : Data::LaneModel;
        }
        action <'SF-EST'> 'Estimate departure' : Types::'Periodic task' {
            attribute latency : DurationValue = 15 [ms];
            attribute wcet : DurationValue = 18 [ms];
            in item lane : Data::LaneModel;
            out item departure : Data::DepartureEstimate;
        }
        action <'SF-CMD'> 'Command steering' : Types::'Periodic task' {
            attribute latency : DurationValue = 10 [ms];
            attribute wcet : DurationValue = 12 [ms];
            in item departure : Data::DepartureEstimate;
        }
        flow 'lane model' of Data::Data from 'SF-DET'.lane to 'SF-EST'.lane;
        flow 'departure estimate' of Data::Data from 'SF-EST'.departure to 'SF-CMD'.departure;
        #Chain action <'FC-LKA'> 'Lane departure reaction' {
            attribute latency_budget : DurationValue = 80 [ms];
            action step1 :> 'SF-DET';
            then action step2 :> 'SF-EST';
            then action step3 :> 'SF-CMD';
        }
        requirement 'REQ-LKA-001' {
            doc /* Steering correction shall be commanded within 80 ms of lane departure detection */
            attribute priority : String = "Critical";
            attribute safety_level : String = "ASIL-B";
        }
    }
    #LA package 'LKA Logical' {
        port def 'LaneModel port' {
            inout item carried : Data::LaneModel;
        }
        part <'LC-CAM'> Camera {
            attribute safety_level : String = "ASIL-B";
            out port lane : 'LaneModel port';
            perform action 'Capture frame' {
                attribute frame_period : DurationValue = 33 [ms];
            }
        }
        part <'LC-CTL'> 'LKA Controller' {
            attribute safety_level : String = "ASIL-B";
            in port lane : 'LaneModel port';
            perform action 'Plan correction';
        }
        connection LaneFlow connect 'LC-CAM'.lane to 'LC-CTL'.lane;
    }
    #PA package 'LKA Physical' {
        #Node part <'PN-CAM'> 'Camera ECU' : Types::ECU {
            attribute ram : StorageCapacityValue = 512 [MB];
        }
        #Node part <'PN-CHS'> 'Chassis ECU' : Types::'Safety ECU' {
            attribute ram : StorageCapacityValue = 64 [MB];
        }
        allocate 'LKA Logical'::'LC-CAM' to 'PN-CAM';
        allocate 'LKA Logical'::'LC-CTL' to 'PN-CHS';
        #Link connection ChassisCAN : Types::'CAN FD bus' connect 'PN-CAM' to 'PN-CHS' {
            attribute load : BinaryDigitRateValue = 600 ['kbit/s'];
        }
    }
    package Types {
        abstract action def 'Periodic task' {
            doc /* instances must provide: wcet, latency */
            attribute period : DurationValue default = 20 [ms];
        }
        abstract part def ECU {
            doc /* instances must provide: ram */
            attribute voltage : ElectricPotentialValue default = 12 [V];
        }
        abstract part def 'Safety ECU' :> ECU {
            attribute safety_level : String default = "ASIL-B";
        }
        abstract connection def 'CAN FD bus' {
            end source;
            end target;
            attribute bandwidth : BinaryDigitRateValue default = 2 ['Mbit/s'];
            attribute protocol : String default = "CAN FD";
        }
    }
    package Safety {
        #Hazard requirement 'Late steering correction' {
            doc /* Correction commanded too late to keep the lane */
            attribute asil : String = "ASIL-B";
            attribute controllability : String = "C2";
            attribute exposure : String = "E4";
            attribute severity : String = "S2";
        }
        dependency mitigated_by from 'Late steering correction' to 'Lane Keeping Assist'::'REQ-LKA-001';
    }
    verification 'TC-LKA-001' {
        doc /* HIL measurement of departure-to-command latency */
        attribute method : String = "test";
        objective {
            verify 'Lane Keeping Assist'::'REQ-LKA-001';
        }
    }
    assert constraint <'CST-LKA-001'> 'Reaction time margin' {
        doc /* Sum of function latencies stays within 80 % of the chain budget */
        ('Lane Keeping Assist'::'SF-DET'.latency + 'Lane Keeping Assist'::'SF-EST'.latency + 'Lane Keeping Assist'::'SF-CMD'.latency) <= ('Lane Keeping Assist'::'FC-LKA'.latency_budget * 0.8)
    }
    assert constraint <'CST-LKA-002'> 'Worst-case reaction time' {
        ('Lane Keeping Assist'::'SF-DET'.wcet + 'Lane Keeping Assist'::'SF-EST'.wcet + 'Lane Keeping Assist'::'SF-CMD'.wcet) <= 'Lane Keeping Assist'::'FC-LKA'.latency_budget
    }
    assert constraint <'CST-LKA-003'> 'Stage fits a camera frame' {
        DataFunctions::max(DataFunctions::max('Lane Keeping Assist'::'SF-DET'.wcet, 'Lane Keeping Assist'::'SF-EST'.wcet), 'Lane Keeping Assist'::'SF-CMD'.wcet) <= ('LKA Logical'::'LC-CAM'.'Capture frame'.frame_period * 1.1)
    }
    assert constraint <'CST-LKA-004'> 'CAN bus load' {
        ('LKA Physical'::ChassisCAN.load / 'LKA Physical'::ChassisCAN.bandwidth) <= 0.4
    }
    assert constraint <'CST-LKA-005'> 'Detection meets its period' {
        'Lane Keeping Assist'::'SF-DET'.wcet <= ('Lane Keeping Assist'::'SF-DET'.period * 1.1)
    }
    satisfy 'Lane Keeping Assist'::'REQ-LKA-001' by 'LKA Logical'::'LC-CTL';
    package ArcLangUnits {
        private import MeasurementReferences::*;
        private import ISQ::*;
        private import SI::*;
        attribute <'Mbit/s'> 'megabit per second' : BinaryDigitRateUnit { :>> unitConversion: ConversionByPrefix { :>> prefix = mega; :>> referenceUnit = 'bit/s'; } }
        attribute <'kbit/s'> 'kilobit per second' : BinaryDigitRateUnit { :>> unitConversion: ConversionByPrefix { :>> prefix = kilo; :>> referenceUnit = 'bit/s'; } }
        attribute <MB> megabyte : StorageCapacityUnit { :>> unitConversion: ConversionByPrefix { :>> prefix = mega; :>> referenceUnit = B; } }
        attribute <ms> millisecond : DurationUnit { :>> unitConversion: ConversionByPrefix { :>> prefix = milli; :>> referenceUnit = s; } }
    }
    private import ArcLangUnits::*;
}
