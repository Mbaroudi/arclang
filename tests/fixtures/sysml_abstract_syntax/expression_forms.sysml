// Generated by ArcLang: SysML v2 in the Arcadia profile (spec/SYSML_PROFILE.md)
package ExpressionForms {
    private import ScalarValues::*;
    private import MeasurementReferences::*;
    private import ISQ::*;
    private import SI::*;
    library package ArcadiaProfile {
        metadata def OA;
        metadata def SA;
        metadata def LA;
        metadata def PA;
        metadata def EPBS;
        metadata def Actor;
        metadata def Entity;
        metadata def Node;
        metadata def Behavior;
        metadata def Hardware;
        metadata def Mission;
        metadata def Capability;
        metadata def Chain;
        metadata def Link;
        metadata def Hazard;
        metadata def Mode;
        metadata def Class;
        metadata def PhysicalPort;
        metadata def ExchangeItem;
        metadata def Path;
        metadata def Fmea;
        metadata def Interface;
        metadata def Trace;
        metadata def Association;
        metadata def Iterate;
        metadata def Invariant;
    }
    private import ArcadiaProfile::*;
    #SA package Forms {
        action <'SF-A'> Sample : Types::Task {
            attribute bandwidth : BinaryDigitRateValue = 2 ['Mbit/s'];
            attribute clock : FrequencyValue = 16 [MHz];
            attribute count : Integer = 3;
            attribute distance : LengthValue = 250 [m];
            attribute energy : EnergyValue = 2 ['kW*h'];
            attribute :>> gain = 2.5;
            attribute label : String = "a \"quoted\" label";
            attribute load : DimensionOneValue = 40 ['%'];
            attribute mass : MassValue = 12 [kg];
            attribute memory : StorageCapacityValue = 512 [MiB];
            attribute offset : Integer = -5;
            attribute :>> period = 10 [ms];
            attribute pressure : PressureValue = 3 [bar];
            attribute rate : BinaryDigitRateValue = 9600 ['bit/s'];
            attribute speed : SpeedValue = 130 ['km/h'];
            attribute supply : ElectricPotentialValue = 12 [V];
            attribute wcet : DurationValue = 0.004 [s];
        }
        action <'SF-B'> Filter : Types::Task {
            attribute wcet : DurationValue = 6 [ms];
        }
        #Chain action <'FC-A'> Acquire {
            attribute latency_budget : DurationValue = 40 [ms];
            action step1 :> 'SF-A';
            then action step2 :> 'SF-B';
        }
    }
    #LA package Multiplicities {
        part <'LC-SNS'> Sensor [2] {
            part <'LC-LNS'> Lens [4];
        }
        part <'LC-BKP'> Backup [0..1];
        part <'LC-CHN'> Channel [1..*];
        part <'LC-PRB'> Probe [*];
        part <'LC-HUB'> Hub;
    }
    #PA package Hardware {
        #Node part <'PN-CPU'> 'Compute unit' [2..3];
    }
    package Types {
        abstract action def Task {
            attribute gain : Real default = 1.5;
            attribute period : DurationValue default = 20 [ms];
        }
    }
    assert constraint <'CST-MIN'> 'Fastest stage' {
        DataFunctions::min(Forms::'SF-A'.wcet, Forms::'SF-B'.wcet) >= 1 [ms]
    }
    assert constraint <'CST-MAX'> 'Slowest stage' {
        (DataFunctions::max(Forms::'SF-A'.wcet, Forms::'SF-B'.wcet) + 2 [ms]) < (Forms::'FC-A'.latency_budget / 2)
    }
    assert constraint <'CST-SUM'> Total {
        ((Forms::'SF-A'.wcet + Forms::'SF-B'.wcet) - (Forms::'SF-B'.wcet * 2)) <= Forms::'SF-A'.period
    }
    assert constraint <'CST-CNT'> Stages {
        2 == 2
    }
    package ArcLangUnits {
        private import MeasurementReferences::*;
        private import ISQ::*;
        private import SI::*;
        attribute <'%'> percent : DimensionOneUnit { :>> unitConversion: ConversionByConvention { :>> referenceUnit = one; :>> conversionFactor = 0.01; } }
        attribute <'Mbit/s'> 'megabit per second' : BinaryDigitRateUnit { :>> unitConversion: ConversionByPrefix { :>> prefix = mega; :>> referenceUnit = 'bit/s'; } }
        attribute <'kW*h'> 'kilowatt hour' : EnergyUnit { :>> unitConversion: ConversionByConvention { :>> referenceUnit = J; :>> conversionFactor = 3600000; } }
        attribute <MHz> megahertz : FrequencyUnit { :>> unitConversion: ConversionByPrefix { :>> prefix = mega; :>> referenceUnit = Hz; } }
        attribute <MiB> mebibyte : StorageCapacityUnit { :>> unitConversion: ConversionByConvention { :>> referenceUnit = B; :>> conversionFactor = 1048576; } }
        attribute <bar> bar : PressureUnit { :>> unitConversion: ConversionByConvention { :>> referenceUnit = Pa; :>> conversionFactor = 100000; } }
        attribute <ms> millisecond : DurationUnit { :>> unitConversion: ConversionByPrefix { :>> prefix = milli; :>> referenceUnit = s; } }
    }
    private import ArcLangUnits::*;
}
