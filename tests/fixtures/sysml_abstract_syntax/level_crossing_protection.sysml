// Generated by ArcLang: SysML v2 in the Arcadia profile (spec/SYSML_PROFILE.md)
package LevelCrossingProtection {
    private import ScalarValues::*;
    private import MeasurementReferences::*;
    private import ISQ::*;
    private import SI::*;
    library package ArcadiaProfile {
        metadata def OA;
        metadata def SA;
        metadata def LA;
        metadata def PA;
        metadata def EPBS;
        metadata def Actor;
        metadata def Entity;
        metadata def Node;
        metadata def Behavior;
        metadata def Hardware;
        metadata def Mission;
        metadata def Capability;
        metadata def Chain;
        metadata def Link;
        metadata def Hazard;
        metadata def Mode;
        metadata def Class;
        metadata def PhysicalPort;
        metadata def ExchangeItem;
        metadata def Path;
        metadata def Fmea;
        metadata def Interface;
        metadata def Trace;
        metadata def Association;
        metadata def Iterate;
        metadata def Invariant;
    }
    private import ArcadiaProfile::*;
    attribute version : String = "1.0";
    package Data {
        item def Data;
    }
    #OA package 'Level Crossing Operations' {
        #Actor part <'OA-ACT-001'> 'Train Driver' {
            doc /* Drives the approaching train */
        }
        #Actor part <'OA-ACT-002'> 'Road User' {
            doc /* Vehicles and pedestrians crossing the track */
        }
        #Actor part <'OA-ACT-003'> Signaller {
            doc /* Supervises the line and handles degraded modes */
        }
        #Capability use case <'OC-001'> 'Protect the crossing' {
            doc /* Road traffic is stopped and proven clear before a train passes */
        }
    }
    #SA package 'Safety Requirements' {
        requirement <'REQ-LX-001'> 'Train detection' {
            doc /* The system shall detect an approaching train at least 30 s before it reaches the crossing */
            attribute priority : String = "High";
        }
        requirement <'REQ-LX-002'> 'Barrier closure' {
            doc /* Barriers shall be fully closed at least 10 s before the train reaches the crossing */
            attribute priority : String = "High";
        }
        requirement <'REQ-LX-003'> 'Crossing clear proving' {
            doc /* The system shall prove the crossing area is free of obstacles before authorizing train passage */
            attribute priority : String = "High";
        }
        requirement <'REQ-LX-004'> 'Fail-safe state' {
            doc /* On any internal failure, barriers shall close and the protecting signal shall show stop */
            attribute priority : String = "High";
        }
    }
    #LA package 'Logical Architecture' {
        port def 'Data port' {
            inout item carried : Data::Data;
        }
        part <'LC-LX-001'> 'Train Detector' {
            out port TrainApproach : 'Data port';
            perform action 'Detect approaching train' {
                attribute latency : DurationValue = 500 [ms];
            }
        }
        part <'LC-LX-002'> 'Crossing Controller' {
            in port TrainApproach : 'Data port';
            in port CrossingStatus : 'Data port';
            out port BarrierCommand : 'Data port';
            out port SignalCommand : 'Data port';
            perform action 'Sequence the protection cycle' {
                attribute latency : DurationValue = 200 [ms];
            }
            perform action 'Enter fail-safe on fault';
        }
        part <'LC-LX-003'> 'Barrier Machine' {
            in port BarrierCommand : 'Data port';
            perform action 'Drive the barriers';
        }
        part <'LC-LX-004'> 'Obstacle Detector' {
            out port CrossingStatus : 'Data port';
            perform action 'Prove crossing clear' {
                attribute latency : DurationValue = 300 [ms];
            }
        }
        part <'LC-LX-005'> 'Protecting Signal' {
            in port SignalCommand : 'Data port';
            perform action 'Display movement authority';
        }
        connection 'train approach' connect 'LC-LX-001' to 'LC-LX-002';
        connection 'crossing status' connect 'LC-LX-004' to 'LC-LX-002';
        connection 'barrier command' connect 'LC-LX-002' to 'LC-LX-003';
        connection 'signal command' connect 'LC-LX-002' to 'LC-LX-005';
    }
    package Behaviors {
        state CrossingModes {
            entry; then Open;
            #Mode state Open;
            #Mode state Closing;
            #Mode state Protected;
            #Mode state Failed;
            transition t1 first Open then Closing {
                attribute trigger : String = "train approach";
            }
            transition t2 first Closing then Protected {
                attribute trigger : String = "crossing status";
            }
            transition t3 first Protected then Open {
                attribute trigger : String = "train approach";
            }
            transition t4 first Closing then Failed {
                attribute trigger : String = "Enter fail-safe on fault";
            }
            transition t5 first Protected then Failed {
                attribute trigger : String = "Enter fail-safe on fault";
            }
        }
    }
    verification 'TC-LX-001' {
        attribute method : String = "test";
        objective {
            verify 'Safety Requirements'::'REQ-LX-001';
        }
    }
    verification 'TC-LX-002' {
        attribute method : String = "analysis";
        objective {
            verify 'Safety Requirements'::'REQ-LX-002';
        }
    }
    verification 'TC-LX-003' {
        attribute method : String = "demonstration";
        objective {
            verify 'Safety Requirements'::'REQ-LX-003';
        }
    }
    verification 'TC-LX-004' {
        attribute method : String = "test";
        objective {
            verify 'Safety Requirements'::'REQ-LX-004';
        }
    }
    satisfy 'Safety Requirements'::'REQ-LX-001' by 'Logical Architecture'::'LC-LX-001';
    satisfy 'Safety Requirements'::'REQ-LX-002' by 'Logical Architecture'::'LC-LX-002';
    satisfy 'Safety Requirements'::'REQ-LX-002' by 'Logical Architecture'::'LC-LX-003';
    satisfy 'Safety Requirements'::'REQ-LX-003' by 'Logical Architecture'::'LC-LX-004';
    satisfy 'Safety Requirements'::'REQ-LX-004' by 'Logical Architecture'::'LC-LX-002';
    package ArcLangUnits {
        private import MeasurementReferences::*;
        private import ISQ::*;
        private import SI::*;
        attribute <ms> millisecond : DurationUnit { :>> unitConversion: ConversionByPrefix { :>> prefix = milli; :>> referenceUnit = s; } }
    }
    private import ArcLangUnits::*;
}
