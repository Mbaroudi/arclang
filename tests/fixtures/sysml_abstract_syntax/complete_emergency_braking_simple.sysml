// Generated by ArcLang: SysML v2 in the Arcadia profile (spec/SYSML_PROFILE.md)
package <EmergencyBrakingSystem> 'Automotive Emergency Braking System (AEB)' {
    private import ScalarValues::*;
    private import MeasurementReferences::*;
    private import ISQ::*;
    private import SI::*;
    library package ArcadiaProfile {
        metadata def OA;
        metadata def SA;
        metadata def LA;
        metadata def PA;
        metadata def EPBS;
        metadata def Actor;
        metadata def Entity;
        metadata def Node;
        metadata def Behavior;
        metadata def Hardware;
        metadata def Mission;
        metadata def Capability;
        metadata def Chain;
        metadata def Link;
        metadata def Hazard;
        metadata def Mode;
        metadata def Class;
        metadata def PhysicalPort;
        metadata def ExchangeItem;
        metadata def Path;
        metadata def Fmea;
        metadata def Interface;
        metadata def Trace;
        metadata def Association;
        metadata def Iterate;
        metadata def Invariant;
    }
    private import ArcadiaProfile::*;
    doc /* Complete MBSE model with all Arcadia layers */
    attribute author : String = "Malek Baroudi";
    attribute safety_standard : String = "ISO 26262 ASIL-D";
    attribute version : String = "2.0.0";
    package Data {
        enum def <'EN-001'> ThreatLevel {
            None;
            Low;
            Critical;
        }
        attribute def <'DT-001'> BrakingForce :> Real {
            attribute base : String = "float";
            attribute unit : String = "N";
        }
        #ExchangeItem item def <'EI-001'> RadarTargets {
            attribute mechanism : String = "FLOW";
            ref item 'element_CL-001' : 'CL-001';
        }
        #ExchangeItem item def <'EI-002'> ThreatAssessed {
            attribute mechanism : String = "EVENT";
            attribute 'element_EN-001' : 'EN-001';
        }
        #ExchangeItem item def <'EI-003'> raw_sensor_data {
            attribute mechanism : String = "FLOW";
            ref item 'element_CL-001' : 'CL-001';
        }
        #ExchangeItem item def <'EI-004'> fused_data {
            attribute mechanism : String = "FLOW";
        }
        #ExchangeItem item def <'EI-005'> tracked_objects {
            attribute mechanism : String = "FLOW";
        }
        #ExchangeItem item def <'EI-006'> threat_level {
            attribute mechanism : String = "EVENT";
            attribute 'element_EN-001' : 'EN-001';
        }
        #ExchangeItem item def <'EI-007'> vehicle_speed {
            attribute mechanism : String = "FLOW";
        }
        #Class item def <'CL-001'> RadarFrame {
            attribute range_m : Real;
            attribute azimuth_deg : Real;
            attribute velocity_mps : Real;
        }
        item def Data;
    }
    #OA package 'Emergency Braking - Operational View' {
        #Entity part <'OE-Vehicle'> Vehicle {
            doc /* The vehicle being controlled */
            perform action <'OA-MonitorEnvironment'> MonitorEnvironment {
                doc /* Continuously observe surroundings */
            }
            perform action <'OA-DetectThreat'> DetectThreat {
                doc /* Identify potential collision hazards */
            }
            perform action <'OA-AlertDriver'> AlertDriver {
                doc /* Warn driver of imminent danger */
            }
            perform action <'OA-ApplyBrakes'> ApplyBrakes {
                doc /* Execute emergency braking */
            }
        }
        #Actor part <'OA-ACT-001'> Driver {
            doc /* Vehicle driver */
            attribute type : String = "human";
        }
        #Actor part <'OA-ACT-002'> Pedestrian {
            doc /* Vulnerable road user */
            attribute type : String = "human";
        }
        #Actor part <'OA-ACT-003'> TrafficEnvironment {
            doc /* Road conditions, weather, other vehicles */
            attribute type : String = "environment";
        }
        #Capability use case <'OC-001'> 'Avoid Collisions' {
            doc /* Ability to avoid collisions with obstacles and vulnerable road users */
        }
        connection DriverCommands connect 'OA-ACT-001' to 'OE-Vehicle'.'OA-MonitorEnvironment';
        connection EnvironmentData connect 'OA-ACT-003' to 'OE-Vehicle'.'OA-MonitorEnvironment';
        flow ThreatDetection of Data::Data from 'OE-Vehicle'.'OA-MonitorEnvironment' to 'OE-Vehicle'.'OA-DetectThreat';
        connection DriverWarning connect 'OE-Vehicle'.'OA-AlertDriver' to 'OA-ACT-001';
        connection BrakingAction connect 'OE-Vehicle'.'OA-ApplyBrakes' to 'OE-Vehicle';
        connection PedestrianProtection connect 'OE-Vehicle'.'OA-ApplyBrakes' to 'OA-ACT-002';
    }
    #SA package 'AEB System - Functional View' {
        action <'SF-AcquireSensorData'> AcquireSensorData {
            doc /* Collect data from radar and camera */
            attribute color : String = "#ADD8E6";
            attribute latency : DurationValue = 20 [ms];
            attribute safety_level : String = "ASIL-D";
        }
        action <'SF-FuseData'> FuseData {
            doc /* Combine multiple sensor inputs */
            attribute color : String = "#ADD8E6";
            attribute latency : DurationValue = 25 [ms];
            attribute safety_level : String = "ASIL-D";
        }
        action <'SF-TrackObjects'> TrackObjects {
            doc /* Track detected objects over time */
            attribute color : String = "#ADD8E6";
            attribute latency : DurationValue = 15 [ms];
            attribute safety_level : String = "ASIL-D";
        }
        action <'SF-AssessThreat'> AssessThreat {
            doc /* Determine collision risk */
            attribute color : String = "#ADD8E6";
            attribute latency : DurationValue = 20 [ms];
            attribute safety_level : String = "ASIL-D";
        }
        action <'SF-GenerateWarning'> GenerateWarning {
            doc /* Create driver warning signals */
            attribute color : String = "#ADD8E6";
            attribute safety_level : String = "ASIL-B";
        }
        action <'SF-ComputeBrakingForce'> ComputeBrakingForce {
            doc /* Calculate required braking force */
            attribute color : String = "#ADD8E6";
            attribute latency : DurationValue = 10 [ms];
            attribute safety_level : String = "ASIL-D";
        }
        action <'SF-MonitorVehicleState'> MonitorVehicleState {
            doc /* Track vehicle speed, steering, etc. */
            attribute color : String = "#ADD8E6";
            attribute safety_level : String = "ASIL-B";
        }
        #Actor part <'SA-ACT-Driver'> Driver {
            doc /* Vehicle operator */
        }
        #Actor part <'SA-ACT-Vehicle'> Vehicle {
            doc /* Vehicle platform */
        }
        connection SensorToFusion connect 'SF-AcquireSensorData' to 'SF-FuseData';
        dependency exchange_item from SensorToFusion to Data::'EI-003';
        connection FusionToTracking connect 'SF-FuseData' to 'SF-TrackObjects';
        dependency exchange_item from FusionToTracking to Data::'EI-004';
        connection TrackingToThreat connect 'SF-TrackObjects' to 'SF-AssessThreat';
        dependency exchange_item from TrackingToThreat to Data::'EI-005';
        connection ThreatToWarning connect 'SF-AssessThreat' to 'SF-GenerateWarning';
        dependency exchange_item from ThreatToWarning to Data::'EI-006';
        connection ThreatToBraking connect 'SF-AssessThreat' to 'SF-ComputeBrakingForce';
        dependency exchange_item from ThreatToBraking to Data::'EI-006';
        connection VehicleToThreat connect 'SF-MonitorVehicleState' to 'SF-AssessThreat';
        dependency exchange_item from VehicleToThreat to Data::'EI-007';
        connection VehicleToBraking connect 'SF-MonitorVehicleState' to 'SF-ComputeBrakingForce';
        dependency exchange_item from VehicleToBraking to Data::'EI-007';
        #Mission use case <'MIS-001'> SafeAutonomousBraking {
            doc /* Prevent collisions through autonomous emergency braking */
        }
        #Capability use case <'CAP-001'> EmergencyBraking {
            doc /* Detect an imminent collision and brake autonomously */
        }
        dependency involves from 'CAP-001' to 'SF-AcquireSensorData';
        dependency involves from 'CAP-001' to 'SF-FuseData';
        dependency involves from 'CAP-001' to 'SF-AssessThreat';
        dependency involves from 'CAP-001' to 'SF-ComputeBrakingForce';
        dependency realizes from 'CAP-001' to 'Emergency Braking - Operational View'::'OC-001';
        dependency mission from 'CAP-001' to 'MIS-001';
        #Chain action <'FC-001'> EmergencyBrakingChain {
            doc /* Sensor acquisition to braking command */
            attribute latency_budget : DurationValue = 100 [ms];
            action step1 :> 'SF-AcquireSensorData';
            then action step2 :> 'SF-FuseData';
            then action step3 :> 'SF-TrackObjects';
            then action step4 :> 'SF-AssessThreat';
            then action step5 :> 'SF-ComputeBrakingForce';
        }
    }
    #SA package 'Safety Requirements' {
        requirement <'REQ-AEB-001'> 'Obstacle detection range' {
            doc /* The system shall detect obstacles at a range of at least 150 m */
            attribute priority : String = "High";
            attribute safety_level : String = "ASIL-D";
        }
        requirement <'REQ-AEB-002'> 'Sensor fusion latency' {
            doc /* Radar and camera data shall be fused within 50 ms */
            attribute priority : String = "High";
            attribute safety_level : String = "ASIL-D";
        }
        requirement <'REQ-AEB-003'> 'Collision risk assessment' {
            doc /* The system shall compute time-to-collision for every tracked object */
            attribute priority : String = "High";
            attribute safety_level : String = "ASIL-D";
        }
        requirement <'REQ-AEB-004'> 'Emergency braking activation' {
            doc /* Full braking force shall be commanded within 100 ms of critical threat detection */
            attribute priority : String = "High";
            attribute safety_level : String = "ASIL-D";
        }
        requirement <'REQ-AEB-005'> 'Driver warning' {
            doc /* The driver shall be warned before autonomous braking is applied */
            attribute priority : String = "Medium";
            attribute safety_level : String = "ASIL-B";
        }
    }
    #LA package 'AEB System - Component Structure' {
        port def Port;
        part <'LC-RadarSensor'> RadarSensor {
            doc /* Front-facing radar sensor */
            attribute color : String = "#6495ED";
            attribute safety_level : String = "ASIL-D";
            attribute type : String = "Sensor";
            out port RadarDataProvider : Port {
                attribute protocol : String = "CAN";
            }
            perform action 'Acquire radar frames';
        }
        part <'LC-CameraSensor'> CameraSensor {
            doc /* Front-facing camera */
            attribute color : String = "#6495ED";
            attribute safety_level : String = "ASIL-D";
            attribute type : String = "Sensor";
            out port CameraDataProvider : Port {
                attribute protocol : String = "Ethernet";
            }
            perform action 'Acquire camera frames';
        }
        part <'LC-SensorFusion'> SensorFusion {
            doc /* Multi-sensor data fusion */
            attribute allocated_function : String = "FuseData";
            attribute color : String = "#6495ED";
            attribute safety_level : String = "ASIL-D";
            attribute type : String = "Processing";
            in port RadarDataConsumer : Port;
            in port CameraDataConsumer : Port;
            out port FusedDataProvider : Port;
            perform action 'Fuse sensor data';
        }
        part <'LC-ObjectTracker'> ObjectTracker {
            doc /* Object tracking and prediction */
            attribute allocated_function : String = "TrackObjects";
            attribute color : String = "#6495ED";
            attribute safety_level : String = "ASIL-D";
            attribute type : String = "Processing";
            in port FusedDataConsumer : Port;
            out port TrackedObjectsProvider : Port;
            perform action 'Track objects';
        }
        part <'LC-ThreatAssessment'> ThreatAssessment {
            doc /* Collision risk assessment */
            attribute allocated_function : String = "AssessThreat";
            attribute color : String = "#6495ED";
            attribute safety_level : String = "ASIL-D";
            attribute type : String = "Decision";
            in port TrackedObjectsConsumer : Port;
            in port VehicleStateConsumer : Port;
            out port ThreatLevelProvider : Port;
            perform action 'Assess collision threat';
        }
        part <'LC-BrakeController'> BrakeController {
            doc /* Emergency brake control */
            attribute allocated_function : String = "ComputeBrakingForce";
            attribute color : String = "#6495ED";
            attribute safety_level : String = "ASIL-D";
            attribute type : String = "Controller";
            in port ThreatLevelConsumer : Port;
            in port VehicleSpeedConsumer : Port;
            out port BrakeCommandProvider : Port;
            perform action 'Compute braking command';
        }
        part <'LC-DriverInterface'> DriverInterface {
            doc /* HMI for warnings */
            attribute allocated_function : String = "GenerateWarning";
            attribute color : String = "#6495ED";
            attribute safety_level : String = "QM";
            attribute type : String = "Interface";
            in port WarningConsumer : Port;
            perform action 'Warn driver';
        }
        part <'LC-VehicleCANGateway'> VehicleCANGateway {
            doc /* CAN bus interface */
            attribute allocated_function : String = "MonitorVehicleState";
            attribute color : String = "#6495ED";
            attribute safety_level : String = "ASIL-B";
            attribute type : String = "Gateway";
            out port VehicleStateProvider : Port;
            out port VehicleSpeedProvider : Port;
            perform action 'Relay vehicle state';
        }
        part <'LC-BrakeActuator'> BrakeActuator {
            doc /* Physical brake actuator */
            attribute color : String = "#6495ED";
            attribute safety_level : String = "ASIL-D";
            attribute type : String = "Actuator";
            in port BrakeCommandConsumer : Port;
            perform action 'Apply braking force';
        }
        connection 'Radar Data' connect 'LC-RadarSensor'.RadarDataProvider to 'LC-SensorFusion'.RadarDataConsumer {
            attribute label : String = "Radar Data";
        }
        connection 'Camera Data' connect 'LC-CameraSensor'.CameraDataProvider to 'LC-SensorFusion'.CameraDataConsumer {
            attribute label : String = "Camera Data";
        }
        connection 'Fused Data' connect 'LC-SensorFusion'.FusedDataProvider to 'LC-ObjectTracker'.FusedDataConsumer {
            attribute label : String = "Fused Data";
        }
        connection 'Tracked Objects' connect 'LC-ObjectTracker'.TrackedObjectsProvider to 'LC-ThreatAssessment'.TrackedObjectsConsumer {
            attribute label : String = "Tracked Objects";
        }
        connection 'Vehicle State' connect 'LC-VehicleCANGateway'.VehicleStateProvider to 'LC-ThreatAssessment'.VehicleStateConsumer {
            attribute label : String = "Vehicle State";
        }
        connection 'Threat Level' connect 'LC-ThreatAssessment'.ThreatLevelProvider to 'LC-BrakeController'.ThreatLevelConsumer {
            attribute label : String = "Threat Level";
        }
        connection 'Vehicle Speed' connect 'LC-VehicleCANGateway'.VehicleSpeedProvider to 'LC-BrakeController'.VehicleSpeedConsumer {
            attribute label : String = "Vehicle Speed";
        }
        connection 'Brake Command' connect 'LC-BrakeController'.BrakeCommandProvider to 'LC-BrakeActuator'.BrakeCommandConsumer {
            attribute label : String = "Brake Command";
        }
    }
    #PA package 'AEB System - Hardware Deployment' {
        #Node part <'PN-FrontRadarECU'> FrontRadarECU {
            doc /* Radar sensor ECU */
            attribute memory : String = "512KB Flash, 128KB RAM";
            attribute node_type : String = "ECU";
            attribute processor : String = "ARM Cortex-M4";
            attribute safety_level : String = "ASIL-D";
            #Behavior part <'BC-RadarProcessing'> RadarProcessing {
                doc /* Radar data acquisition and preprocessing */
                attribute component_type : String = "Behavior";
                attribute safety_level : String = "ASIL-D";
            }
        }
        #Node part <'PN-FrontCameraECU'> FrontCameraECU {
            doc /* Camera sensor ECU */
            attribute memory : String = "2GB DDR4";
            attribute node_type : String = "ECU";
            attribute processor : String = "ARM Cortex-A53";
            attribute safety_level : String = "ASIL-D";
            #Behavior part <'BC-CameraProcessing'> CameraProcessing {
                doc /* Camera image processing and object detection */
                attribute component_type : String = "Behavior";
                attribute safety_level : String = "ASIL-D";
            }
        }
        #Node part <'PN-CentralADASECU'> CentralADASECU {
            doc /* Central ADAS processing unit */
            attribute memory : String = "8GB DDR4, 64GB eMMC";
            attribute node_type : String = "ECU";
            attribute processor : String = "Intel Atom x5-E3940";
            attribute safety_level : String = "ASIL-D";
            #Behavior part <'BC-FusionModule'> FusionModule {
                attribute component_type : String = "Behavior";
                attribute safety_level : String = "ASIL-D";
            }
            #Behavior part <'BC-TrackingModule'> TrackingModule {
                attribute component_type : String = "Behavior";
                attribute safety_level : String = "ASIL-D";
            }
            #Behavior part <'BC-ThreatModule'> ThreatModule {
                attribute component_type : String = "Behavior";
                attribute safety_level : String = "ASIL-D";
            }
            #Behavior part <'BC-BrakingModule'> BrakingModule {
                attribute component_type : String = "Behavior";
                attribute safety_level : String = "ASIL-D";
            }
        }
        #Node part <'PN-BrakeECU'> BrakeECU {
            doc /* Electronic Brake Control Unit */
            attribute memory : String = "8MB Flash, 3MB RAM";
            attribute node_type : String = "ECU";
            attribute processor : String = "Infineon AURIX TC397";
            attribute safety_level : String = "ASIL-D";
            #Behavior part <'BC-BrakeActuation'> BrakeActuation {
                attribute component_type : String = "Behavior";
                attribute safety_level : String = "ASIL-D";
            }
        }
        #Node part <'PN-InstrumentCluster'> InstrumentCluster {
            doc /* Driver display and HMI */
            attribute memory : String = "4GB DDR4";
            attribute node_type : String = "ECU";
            attribute processor : String = "NXP i.MX 8M";
            attribute safety_level : String = "QM";
            #Behavior part <'BC-HMI'> HMI {
                attribute component_type : String = "Behavior";
                attribute safety_level : String = "QM";
            }
        }
        #Node part <'PN-CANGatewayECU'> CANGatewayECU {
            doc /* Vehicle CAN gateway */
            attribute memory : String = "2MB Flash";
            attribute node_type : String = "Gateway";
            attribute processor : String = "Renesas RH850";
            attribute safety_level : String = "ASIL-B";
            #Behavior part <'BC-CANInterface'> CANInterface {
                attribute component_type : String = "Behavior";
                attribute safety_level : String = "ASIL-B";
            }
        }
        allocate 'AEB System - Component Structure'::'LC-RadarSensor' to 'PN-FrontRadarECU';
        dependency allocated_component from 'PN-FrontRadarECU'::'BC-RadarProcessing' to 'AEB System - Component Structure'::'LC-RadarSensor';
        allocate 'AEB System - Component Structure'::'LC-CameraSensor' to 'PN-FrontCameraECU';
        dependency allocated_component from 'PN-FrontCameraECU'::'BC-CameraProcessing' to 'AEB System - Component Structure'::'LC-CameraSensor';
        allocate 'AEB System - Component Structure'::'LC-SensorFusion' to 'PN-CentralADASECU';
        allocate 'AEB System - Component Structure'::'LC-ObjectTracker' to 'PN-CentralADASECU';
        allocate 'AEB System - Component Structure'::'LC-ThreatAssessment' to 'PN-CentralADASECU';
        allocate 'AEB System - Component Structure'::'LC-BrakeController' to 'PN-CentralADASECU';
        dependency allocated_component from 'PN-CentralADASECU'::'BC-FusionModule' to 'AEB System - Component Structure'::'LC-SensorFusion';
        dependency allocated_component from 'PN-CentralADASECU'::'BC-TrackingModule' to 'AEB System - Component Structure'::'LC-ObjectTracker';
        dependency allocated_component from 'PN-CentralADASECU'::'BC-ThreatModule' to 'AEB System - Component Structure'::'LC-ThreatAssessment';
        dependency allocated_component from 'PN-CentralADASECU'::'BC-BrakingModule' to 'AEB System - Component Structure'::'LC-BrakeController';
        allocate 'AEB System - Component Structure'::'LC-BrakeActuator' to 'PN-BrakeECU';
        dependency allocated_component from 'PN-BrakeECU'::'BC-BrakeActuation' to 'AEB System - Component Structure'::'LC-BrakeActuator';
        allocate 'AEB System - Component Structure'::'LC-DriverInterface' to 'PN-InstrumentCluster';
        dependency allocated_component from 'PN-InstrumentCluster'::'BC-HMI' to 'AEB System - Component Structure'::'LC-DriverInterface';
        allocate 'AEB System - Component Structure'::'LC-VehicleCANGateway' to 'PN-CANGatewayECU';
        dependency allocated_component from 'PN-CANGatewayECU'::'BC-CANInterface' to 'AEB System - Component Structure'::'LC-VehicleCANGateway';
        #Link connection CANBus connect 'PN-FrontRadarECU' to 'PN-CentralADASECU' {
            attribute bandwidth : BinaryDigitRateValue = 5 ['Mbit/s'];
            attribute protocol : String = "CAN FD";
        }
        #Link connection EthernetLink connect 'PN-FrontCameraECU' to 'PN-CentralADASECU' {
            attribute bandwidth : BinaryDigitRateValue = 1 ['Gbit/s'];
            attribute protocol : String = "Automotive Ethernet";
        }
        #Link connection BrakeCAN connect 'PN-CentralADASECU' to 'PN-BrakeECU' {
            attribute bandwidth : BinaryDigitRateValue = 5 ['Mbit/s'];
            attribute protocol : String = "CAN FD";
        }
        #Link connection VehicleCAN connect 'PN-CANGatewayECU' to 'PN-CentralADASECU' {
            attribute bandwidth : BinaryDigitRateValue = 500 ['kbit/s'];
            attribute protocol : String = "CAN";
        }
        #Link connection DisplayLink connect 'PN-CentralADASECU' to 'PN-InstrumentCluster' {
            attribute bandwidth : BinaryDigitRateValue = 3.2 ['Gbit/s'];
            attribute pixel_clock : String = "135 MHz";
            attribute protocol : String = "LVDS";
        }
        connection RadarMessages connect 'PN-FrontRadarECU' to 'PN-CentralADASECU' {
            attribute frequency : FrequencyValue = 50 [Hz];
            attribute message_type : String = "RadarTargets";
        }
        dependency 'via' from RadarMessages to CANBus;
        connection CameraMessages connect 'PN-FrontCameraECU' to 'PN-CentralADASECU' {
            attribute frequency : FrequencyValue = 30 [Hz];
            attribute message_type : String = "CameraFrame";
        }
        dependency 'via' from CameraMessages to EthernetLink;
        connection BrakeCommands connect 'PN-CentralADASECU' to 'PN-BrakeECU' {
            attribute frequency : FrequencyValue = 100 [Hz];
            attribute message_type : String = "BrakeRequest";
        }
        dependency 'via' from BrakeCommands to BrakeCAN;
        connection VehicleStatus connect 'PN-CANGatewayECU' to 'PN-CentralADASECU' {
            attribute frequency : FrequencyValue = 100 [Hz];
            attribute message_type : String = "VehicleSpeed";
        }
        dependency 'via' from VehicleStatus to VehicleCAN;
    }
    package Behaviors {
        state AEBOperatingModes {
            entry; then Standby;
            #Mode state Standby {
                doc /* System armed, monitoring */
            }
            #Mode state Warning {
                doc /* Threat detected, driver warned */
            }
            #Mode state EmergencyBraking {
                doc /* Autonomous braking active */
            }
            state Failed {
                doc /* Undergone: sensor or actuator failure */
            }
            transition t1 first Standby then Warning {
                attribute trigger : String = "AssessThreat";
            }
            transition t2 first Warning then EmergencyBraking {
                attribute trigger : String = "ComputeBrakingForce";
            }
            transition t3 first EmergencyBraking then Standby {
                attribute trigger : String = "MonitorVehicleState";
            }
            transition t4 first Standby then Failed {
                attribute guard : String = "sensor_fault";
                attribute trigger : String = "MonitorVehicleState";
            }
        }
        occurrence EmergencyStop {
            ref part l_RadarSensor :> 'AEB System - Component Structure'::'LC-RadarSensor' {
                event occurrence m1_sent;
            }
            ref part l_SensorFusion :> 'AEB System - Component Structure'::'LC-SensorFusion' {
                event occurrence m1_received;
                then event occurrence m2_sent;
            }
            ref part l_ThreatAssessment :> 'AEB System - Component Structure'::'LC-ThreatAssessment' {
                event occurrence m2_received;
                then event occurrence m3_sent;
            }
            ref part l_BrakeController :> 'AEB System - Component Structure'::'LC-BrakeController' {
                event occurrence m3_received;
                then event occurrence m4_sent;
            }
            ref part l_BrakeActuator :> 'AEB System - Component Structure'::'LC-BrakeActuator' {
                event occurrence m4_received;
            }
            message <m1> 'raw radar targets' from l_RadarSensor.m1_sent to l_SensorFusion.m1_received;
            message <m2> 'fused object list' from l_SensorFusion.m2_sent to l_ThreatAssessment.m2_received;
            message <m3> 'critical threat' from l_ThreatAssessment.m3_sent to l_BrakeController.m3_received;
            message <m4> 'full braking force' from l_BrakeController.m4_sent to l_BrakeActuator.m4_received;
        }
    }
    package Safety {
        #Hazard requirement <'HAZ-001'> 'Unintended full braking on highway' {
            attribute asil : String = "ASIL-D";
            attribute controllability : String = "C3";
            attribute exposure : String = "E4";
            attribute severity : String = "S3";
        }
        dependency mitigated_by from 'HAZ-001' to 'Safety Requirements'::'REQ-AEB-003';
        dependency mitigated_by from 'HAZ-001' to 'Safety Requirements'::'REQ-AEB-004';
        #Hazard requirement <'HAZ-002'> 'No braking on imminent collision' {
            attribute asil : String = "ASIL-C";
            attribute controllability : String = "C3";
            attribute exposure : String = "E3";
            attribute severity : String = "S3";
        }
        dependency mitigated_by from 'HAZ-002' to 'Safety Requirements'::'REQ-AEB-001';
        dependency mitigated_by from 'HAZ-002' to 'Safety Requirements'::'REQ-AEB-002';
        #Hazard requirement <'HAZ-003'> 'Late driver warning' {
            attribute asil : String = "ASIL-B";
            attribute controllability : String = "C2";
            attribute exposure : String = "E4";
            attribute severity : String = "S2";
        }
        dependency mitigated_by from 'HAZ-003' to 'Safety Requirements'::'REQ-AEB-005';
    }
    verification <'TC-001'> 'Radar range verification' {
        doc /* Verify 150 m obstacle detection on the proving ground */
        attribute method : String = "test";
        objective {
            verify 'Safety Requirements'::'REQ-AEB-001';
        }
    }
    verification <'TC-002'> 'Fusion latency measurement' {
        doc /* Measure radar+camera fusion latency under full bus load */
        attribute method : String = "test";
        objective {
            verify 'Safety Requirements'::'REQ-AEB-002';
        }
    }
    verification <'TC-003'> 'TTC computation analysis' {
        doc /* Worst-case execution time analysis of the TTC algorithm */
        attribute method : String = "analysis";
        objective {
            verify 'Safety Requirements'::'REQ-AEB-003';
        }
    }
    verification <'TC-004'> 'Emergency braking activation test' {
        doc /* Full braking force commanded within 100 ms on target dummy */
        attribute method : String = "test";
        objective {
            verify 'Safety Requirements'::'REQ-AEB-004';
        }
    }
    verification <'TC-005'> 'Driver warning demonstration' {
        doc /* Visual and audio warning precedes autonomous braking */
        attribute method : String = "demonstration";
        objective {
            verify 'Safety Requirements'::'REQ-AEB-005';
        }
    }
    satisfy 'Safety Requirements'::'REQ-AEB-001' by 'AEB System - Component Structure'::'LC-RadarSensor';
    satisfy 'Safety Requirements'::'REQ-AEB-001' by 'AEB System - Component Structure'::'LC-CameraSensor';
    satisfy 'Safety Requirements'::'REQ-AEB-002' by 'AEB System - Component Structure'::'LC-SensorFusion';
    satisfy 'Safety Requirements'::'REQ-AEB-003' by 'AEB System - Component Structure'::'LC-ThreatAssessment';
    satisfy 'Safety Requirements'::'REQ-AEB-004' by 'AEB System - Component Structure'::'LC-BrakeController';
    satisfy 'Safety Requirements'::'REQ-AEB-005' by 'AEB System - Component Structure'::'LC-DriverInterface';
    #Trace dependency realizes from 'AEB System - Functional View'::'SF-AcquireSensorData' to 'Emergency Braking - Operational View'::'OE-Vehicle'::'OA-MonitorEnvironment';
    #Trace dependency realizes from 'AEB System - Functional View'::'SF-AssessThreat' to 'Emergency Braking - Operational View'::'OE-Vehicle'::'OA-DetectThreat';
    #Trace dependency realizes from 'AEB System - Functional View'::'SF-ComputeBrakingForce' to 'Emergency Braking - Operational View'::'OE-Vehicle'::'OA-ApplyBrakes';
    package ArcLangUnits {
        private import MeasurementReferences::*;
        private import ISQ::*;
        private import SI::*;
        attribute <'Gbit/s'> 'gigabit per second' : BinaryDigitRateUnit { :>> unitConversion: ConversionByPrefix { :>> prefix = giga; :>> referenceUnit = 'bit/s'; } }
        attribute <'Mbit/s'> 'megabit per second' : BinaryDigitRateUnit { :>> unitConversion: ConversionByPrefix { :>> prefix = mega; :>> referenceUnit = 'bit/s'; } }
        attribute <'kbit/s'> 'kilobit per second' : BinaryDigitRateUnit { :>> unitConversion: ConversionByPrefix { :>> prefix = kilo; :>> referenceUnit = 'bit/s'; } }
        attribute <ms> millisecond : DurationUnit { :>> unitConversion: ConversionByPrefix { :>> prefix = milli; :>> referenceUnit = s; } }
    }
    private import ArcLangUnits::*;
}
